(defun c:VXAXIS () (AlignOnAxis "X" 'avg))
(defun c:VYAXIS () (AlignOnAxis "Y" 'avg))
(defun c:AXAXIS () (AlignOnAxis "X" 'ref))
(defun c:AYAXIS () (AlignOnAxis "Y" 'ref))

(defun GetSelection ( / mSel)
  (setq mSel (ssget "_I"))
  (if (null mSel)
    (progn
      (prompt "\nSelect objects to align\n")
      (setq mSel (ssget))
    )
  )
  (if (null mSel)
    (progn (princ "\nNo Selection")(princ)(exit))
  )
  mSel
)

(defun GetRefSelect (/ mSel)
  (prompt "\nSelect reference object\n")
  (setq mSel (ssget))
  (if (null mSel)
    (progn (princ "\nNo Selection")(princ)(exit))  
  )
  (if (> (sslength mSel) 1)
    (progn (princ "\nSelect a single reference object")(princ)(exit))
  )
  mSel
)

(defun GetBasePoint (mObj)
  (if (vlax-property-available-p mObj 'InsertionPoint)
    (vlax-get mObj 'InsertionPoint)
    (progn
      (princ "\nNo insertion point")
      (exit)
    )
  )
)

(defun AlignOnAxis (alax mode / tarCoor refPt refPtU mSelection mOb i msi)
  (setq mSelection (GetSelection))
  (command "_.UNDO" "_Begin")
  (setq *undo-active* T)
  (if (= mode 'ref)
    (setq tarCoor (GetReferencePoint alax))
    (setq tarCoor (GetAvgPoint mSelection alax))
  )
  (setq i 0)
  (while (< i (sslength mSelection))
    (setq msi (ssname mSelection i))
    (setq mOb (vlax-ename->vla-object msi))
    (AlignEntity mOb alax tarCoor)
    (setq i (1+ i))
  )
  (command "_.UNDO" "_End")
  (setq *undo-active* nil)
  (princ)
)

(defun AlignEntity (mObj axis tCoord / dx dy bpt bptU newPt newPtU)
  (setq bpt (GetBasePoint mObj))
  (setq bptU (trans bpt 0 1))
  (if (= axis "X")
    (progn
      (setq dx (- tCoord (car bptU)))
      (setq dy 0.0)
    )
    (progn
      (setq dx 0.0)
      (setq dy (- tCoord (cadr bptU)))
    )
  )
  (setq newPtU (list (+ (car bptU) dx) (+ (cadr bptU) dy) (caddr bptU)))
  (setq newPt (trans newPtU 1 0))
  (vla-move mObj
    (vlax-3d-point bpt)
    (vlax-3d-point newPt)
  )  
)

(defun GetAvgPoint (selSet axis / coordSum count i bp obj bpU)
  (setq coordSum 0.0)
  (setq count (sslength selSet))
  (setq i 0)
  (while (< i count)
    (setq obj (vlax-ename->vla-object (ssname selSet i)))
    (setq bp (GetBasePoint obj))
    (setq bpU (trans bp 0 1))
    (setq coordSum (+ coordSum (if (= axis "X") (car bpU) (cadr bpU))))
    (setq i (1+ i))
  )
  (/ coordSum count)
)

(defun GetReferencePoint (alax / rfSel refPt refPtU)
  (setq rfSel (GetRefSelect))
  (setq refPt (GetBasePoint (vlax-ename->vla-object (ssname rfSel 0))))
  (setq refPtU (trans refPt 0 1))
  (if (= alax "X")
    (car refPtU)
    (cadr refPtU)
  )
)

(defun *error* (msg)
  (if *undo-active*
    (command "_.UNDO" "_End")
  )
  (if (not (wcmatch (strcase msg) "*CANCEL*,*QUIT*"))
    (princ (strcat "\nError: " msg))
  )
  (princ)
)
