(defun GetSelection ( / mSel)
  (prompt "\nSelect objects to align\n")
  (setq mSel (ssget))
  (if (null mSel)
    (progn (princ "\nNo Selection")(princ)(exit))  
  )
  mSel
)
(defun GetRefSelect (/ mSel)
  (prompt "\nSelect reference object\n")
  (setq mSel (ssget))
  (if (null mSel)
    (progn (princ "\nNo Selection")(princ)(exit))  
  )
  (if (> (sslength mSel) 1)
    (progn (princ "\nSelect a single reference object")(princ)(exit))
  )
  mSel
)

(defun GetBasePoint (mObj)
  (if (vlax-property-available-p mObj 'InsertionPoint)
    (vlax-get mObj 'InsertionPoint)
    (progn
      (princ "\nNo insertion point")
      (exit)
    )
  )
)

(defun c:VXAXIS (/ mSelection i msi alax tarCoor mOb)
  (command "_.UNDO" "_Begin")
  (setq mSelection (GetSelection))
  (setq alax "X")
  (setq tarCoor (GetAvgPoint mSelection alax))
  (setq i 0)
  (while (< i (sslength mSelection))
    (setq msi (ssname mSelection i))
    (setq mOb (vlax-ename->vla-object msi))
    (AlignEntity mOb alax tarCoor)
    (setq i (1+ i))  
  )
  (command "_.UNDO" "_End")
)

(defun c:VYAXIS (/ mSelection i msi alax tarCoor mOb)
  (command "_.UNDO" "_Begin")
  (setq mSelection (GetSelection))
  (setq alax "Y")
  (setq tarCoor (GetAvgPoint mSelection alax))
  (setq i 0)
  (while (< i (sslength mSelection))
    (setq msi (ssname mSelection i))
    (setq mOb (vlax-ename->vla-object msi))
    (AlignEntity mOb alax tarCoor)
    (setq i (1+ i))  
  )
  (command "_.UNDO" "_End")
)

(defun c:AXAXIS (/ mSelection i msi alax tarCoor mOb rfSel refPt refPtU)
  (command "_.UNDO" "_Begin")
  (setq mSelection (GetSelection))
  (setq rfSel (GetRefSelect))
  (setq alax "X")
  (setq refPt (GetBasePoint (vlax-ename->vla-object (ssname rfSel 0))))
  (setq refPtU (trans refPt 0 1))
  (setq tarCoor (car refPtU))
  (setq i 0)
  (while (< i (sslength mSelection))
    (setq msi (ssname mSelection i))
    (setq mOb (vlax-ename->vla-object msi))
    (AlignEntity mOb alax tarCoor)
    (setq i (1+ i))
  )
  (command "_.UNDO" "_End")
)

(defun c:AYAXIS (/ mSelection i msi alax tarCoor mOb rfSel refPt refPtU)
  (command "_.UNDO" "_Begin")
  (setq mSelection (GetSelection))
  (setq rfSel (GetRefSelect))
  (setq alax "Y")
  (setq refPt (GetBasePoint (vlax-ename->vla-object (ssname rfSel 0))))
  (setq refPtU (trans refPt 0 1))
  (setq tarCoor (cadr refPtU))
  (setq i 0)
  (while (< i (sslength mSelection))
    (setq msi (ssname mSelection i))
    (setq mOb (vlax-ename->vla-object msi))
    (AlignEntity mOb alax tarCoor)
    (setq i (1+ i))
  )
  (command "_.UNDO" "_End")
)

(defun AlignEntity (mObj axis tCoord / dx dy bpt bptU newPt newPtU)
  (setq bpt (GetBasePoint mObj))
  (setq bptU (trans bpt 0 1))
  (if (= axis "X")
    (progn
      (setq dx (- tCoord (car bptU)))
      (setq dy 0.0)
    )
    (progn
      (setq dx 0.0)
      (setq dy (- tCoord (cadr bptU)))
    )
  )
  (setq newPtU (list (+ (car bptU) dx) (+ (cadr bptU) dy) (caddr bptU)))
  (setq newPt (trans newPtU 1 0))
  (vla-move mObj
    (vlax-3d-point bpt)
    (vlax-3d-point newPt)
  )  
)

(defun GetAvgPoint (selSet axis / coordSum count i bp obj bpU)
  (setq coordSum 0.0)
  (setq count (sslength selSet))
  (setq i 0)
  (while (< i count)
    (setq obj (vlax-ename->vla-object (ssname selSet i)))
    (setq bp (GetBasePoint obj))
    (setq bpU (trans bp 0 1))
    (setq coordSum (+ coordSum (if (= axis "X") (car bpU) (cadr bpU))))
    (setq i (1+ i))
  )
  (/ coordSum count)
)

(defun *error* (msg)
  (command "_.UNDO" "_End")
  (princ (strcat "\nError: " msg))
  (princ)
)
